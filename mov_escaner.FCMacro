##############################################################################
# Mov escaner
# ===========
#
# Description :
#  Recibe del Arduino los valores de los potes 
#  y modifica, segun estos datos, la posicion 
#  del modelo 3d del escaner en el FreeCAD
#  
# Author :
#  Hugo Arboleas <harboleas@citedef.gob.ar>
#
##############################################################################
# 
# Copyright 2016 Hugo Arboleas
#
# This program is free software: you can redistribute it and/or modify
# it under the terms of the GNU Lesser General Public License as published by
# the Free Software Foundation, either version 3 of the License, or
# (at your option) any later version.
#
# This program is distributed in the hope that it will be useful,
# but WITHOUT ANY WARRANTY; without even the implied warranty of
# MERCHANTABILITY or FITNESS FOR A PARTICULAR PURPOSE.  See the
# GNU Lesser General Public License for more details.
#
# You should have received a copy of the GNU Lesser General Public License
# along with this program.  If not, see <http://www.gnu.org/licenses/>.
#
#############################################################################
import FreeCAD 
from PySide import QtGui, QtCore
import struct
import serial
import time
import math
import Draft

RADIANES_POR_CUENTA_1 = math.radians(69) / 214.5
RADIANES_POR_CUENTA_2 = math.radians(59.5) / 214.5
RADIANES_POR_CUENTA_3 = math.radians(90) / 425


doc = FreeCAD.ActiveDocument

# Creo 3 objetos Placement para las rotaciones
rot1 = FreeCAD.Placement()
rot2 = FreeCAD.Placement()
rot3 = FreeCAD.Placement()


# Partes moviles del escaner
acople = doc.Body001
pote2 = doc.Part__Feature002
tuerca2 = doc.Part__Feature003
brazo1 = doc.Body002
pote3 = doc.Part__Feature004
tuerca3 = doc.Part__Feature005
brazo2 = doc.Body003

partes_rot1 = [acople, pote2, tuerca2, brazo1, pote3, tuerca3, brazo2]
orig = [parte.Placement for parte in partes_rot1]

partes_rot1_orig = zip(partes_rot1, orig)
partes_rot2 = partes_rot1[3:]
partes_rot3 = partes_rot2[3:]


rot1.Rotation.Axis = FreeCAD.Vector(0,0,1)

z = FreeCAD.Vector(0,0,1)

punto_orig = FreeCAD.Vector(0, -49.4, 3.9)


# Reset del Arduino para una conexion limpia
arduino = serial.Serial("/dev/ttyUSB0")
arduino.setDTR(False)
time.sleep(1)
arduino.flushInput()
arduino.setDTR(True)
arduino.close()

arduino = serial.Serial("/dev/ttyUSB0", 115200)

arduino.read(1)  # espera que el arduino este listo

puntos = []

def read_pote() :

    datos = arduino.read(2)
    return struct.unpack("h", datos)[0]  # convierte 2 bytes a int

def update() :    # Actualiza el modelo segun los datos leidos


    arduino.write("a") # pide los datos al arduino

    # Lee el valor de los potes y lo convierte a radianes
    p1 = read_pote() * RADIANES_POR_CUENTA_1 
    p3 = read_pote() * RADIANES_POR_CUENTA_3 - math.radians(35)
    p2 = read_pote() * RADIANES_POR_CUENTA_2 - math.radians(35)

    print "%f %f %f" % (math.degrees(p1), math.degrees(p2), math.degrees(p3))

    # Rotacion pote 1
    rot1.Rotation.Angle = p1

    for parte, orig in partes_rot1_orig :
        parte.Placement = rot1.multiply(orig)    

    punto = rot1.multVec(punto_orig)

    # Rotacion pote 2
    rot2.Rotation.Axis = pote2.Placement.Rotation.multVec(z)
    rot2.Rotation.Angle = p2
    rot2.Base = pote2.Placement.Base
    despl = rot2.Base.negative()

    for parte in partes_rot2 :
        parte.Placement.move(despl)
        parte.Placement = rot2.multiply(parte.Placement)    

    punto = punto.add(despl)
    punto = rot2.multVec(punto)   

    # Rotacion pote 3
    rot3.Rotation.Axis = pote3.Placement.Rotation.multVec(z)
    rot3.Rotation.Angle = p3
    rot3.Base = pote3.Placement.Base
    despl = rot3.Base.negative()

    for parte in partes_rot3 :
        parte.Placement.move(despl)
        parte.Placement = rot3.multiply(parte.Placement)    

    punto = punto.add(despl)
    punto = rot3.multVec(punto)   

    puntos.append(punto)

# Actualiza los datos cada 15 ms
timer = QtCore.QTimer()
QtCore.QObject.connect(timer, QtCore.SIGNAL("timeout()"), update)
timer.start(15)
QtGui.QMessageBox.information(None, "", "Tomando puntos")
timer.stop()
arduino.close()

a = file("puntos.xyz", "w")

for p in puntos :
    a.write("%f %f %f\n" % (p.x, p.y, p.z))

a.close()

#  vim: set ts=8 sw=4 tw=0 et :
